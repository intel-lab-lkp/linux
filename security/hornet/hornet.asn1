-- SPDX-License-Identifier: BSD-3-Clause
--
-- Copyright (C) 2009 IETF Trust and the persons identified as authors
-- of the code
--
-- https://www.rfc-editor.org/rfc/rfc5652#section-3

HornetData ::= SET OF Map

Map ::= SEQUENCE {
	index			INTEGER ({ hornet_map_index }),
	sha			OCTET STRING ({ hornet_map_hash })
} ({ hornet_next_map })
